# Car_Headlight_Req

# Specification: Specification Document
- Description: Requirements Document

## R1 (Requirement Type)
Functional Requirements

### R11 (Requirement Type)
The Headlamps produce white light

### R7 (Requirement Type)
In right-traffic countries, the headlamp directs most of the light downward/rightward
- Optional: false

### R8 (Requirement Type)
In left-traffic countries, the headlamp directs most of the light downward/leftward
- Optional: false

### R4 (Requirement Type)
The high beam headlamps provides a bright, centre-weighted distribution of light

#### R5 (Requirement Type)
In the European market, high-beam intensity values must be at least 20,000 cd and at most 75.000 cd

#### R6 (Requirement Type)
In the Canadian market, high-beam intensity values must be at least 30,000 cd and at most 140.000 cd

#### R13 (Requirement Type)
The high beam can have an assistant for automatically turning on/off the high beams
- Optional: true

##### R12 (Requirement Type)
The high beam assistant detects the headlight of forthcomming vehicles from a distance of 1000 m
- Optional: true
- links to -> R16

##### R14 (Requirement Type)
The high beam assistant detects the backlight of vehicles ahead from a distance of 500 m
- Optional: true
- links to -> R15

##### R16 (Requirement Type)
The high beam assistant turn off the high beams if forthcomming vehicles are detected
- Optional: true

##### R15 (Requirement Type)
The high beam assistant temporarily turn off the high beams if vehicles ahead are detected
- Optional: true

##### R23 (Requirement Type)
The high beam assistant can be turned on/off by the user
- Optional: true

### R10 (Requirement Type)
In the European and Canadian market, functionally dedicated daytime running light is required
- Optional: true

### R19 (Requirement Type)
The user can control the car headlight

#### R17: High beams control (Requirement Type)
The user can turn on/off the high beams

#### R28: Dim Light Control (Requirement Type)
The user can turn on/off the dim light

#### R29 (Requirement Type)
The user can turn on/off the parking light

#### R18 (Requirement Type)
The user can turn on /off the fog light
- Optional: true

#### R22 (Requirement Type)
The user can turn on/off the high beam assistant
- Optional: true

#### R20 (Requirement Type)
The user can turn on/off the daytime running light
- Optional: true

#### R24 (Requirement Type)
The user can turn on/off the turn signal

### R27 (Requirement Type)
The parking light increase the visibility of the car

#### R30 (Requirement Type)
The parking light considers the turn signal position: If parking light and turn signal are active, only the according side of the parking light glows

### R32 (Requirement Type)
The static cornering light considers the position of the steering wheel
- Optional: true

## R9 (Requirement Type)
Non-Functional Requirements

### R2 (Requirement Type)
Response: The system must react to user inputs via display or switches within 500 ms

### R3 (Requirement Type)
Availability: The system services shall have an avaiability of 99,99%

## R21 (Requirement Type)
The parking light considers the turn signal position

## R25 (Requirement Type)
The user can turn on/off the dim light

## R26 (Requirement Type)
The user can turn on/off the parking light

## R31
